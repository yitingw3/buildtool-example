# shortest_path_tests_reqs

## #1: Overview (Informational)
This is the test requirements derived from the functional requirements

## #2: Test Cases (Container)

### #15: Tests for invalid conditions (Container)

#### #11: Test a degenerate graph without nodes (Functional)
Any possible value of startIdx and endIdx will be invalid.

#### #14: Test with invalid startIdx <1 (Functional)
Returns -199

#### #18: Test with invalid startIdx > N (Functional)

#### #20: Test with invalid endIdx > N (Functional)

#### #21: Test with invalid endIdx < 1 (Functional)

### #22: Nominal Mode Tests (Container)

#### #3: Test when shortest path is not unique (Functional)

#### #4: Test for path length N where N is number of nodes (largest possible path) (Functional)

#### #5: Test for a graph that contains cycles (Functional)

#### #6: Test for a simple graph with no cycles (Functional)

#### #7: Test for a graph that is a tree (Functional)

#### #8: Test for path length 1 (Functional)

#### #10: Test a graph which has no edges (Functional)
In this situation the return value should be -1 whenever startIdx is not equal to endIdx.

#### #12: Test a graph starting from a node with no edges (Functional)
the return value should be -1.

#### #13: Test a graph ending on a node with no edges (Functional)
Returns -99
