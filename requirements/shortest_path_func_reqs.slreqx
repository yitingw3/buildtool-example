# shortest_path_func_reqs

## #1: Overview (Informational)
We need a function to compute the shortest path through a graph from a start node index to an end node index. The graph is specified by an adjacency matrix and nodes are identified by their index in that graph:
pathLength = shortest_path(adjMatrix, startIdx, endIdx)
The interface should be as follows:
| Input Argument | Type | Dimension |
| --- | --- | --- |
| adjMatrix | double | 1x1 scalar |
| startIdx | double | 1x1 scalar |
| endIdx | double | NxN matrix |
| Output | Type | Dimension |
| pathLength | double | 1x1 scalar |

## #2: Functional behavior (Container)

### #8: Exceptional conditions (Container)
The following exceptional cases should be processed in the order specified where negative value error codes are returned.
The function should be designed so that it never throws an error and always returns a non-negative number to indicate a path or a negative number to indicate some abnormal condition.

#### #4: Returns -1 if no path from startIdx to endIdx exists (Functional)

#### #5: Returns 0 if startIdx == endIdx (Functional)
Every node is implitly assumed to be directed to itself with a path of length 0. Even if that node has no edges.

#### #6: Returns -99 if startIdx or endIdx > number of rows of Adj (Functional)

#### #7: Returns -199 if startIdx or endIdx are < 1 (Functional)

#### #9: Returns -9 for invalid adjacency matrices (Functional)
Valid adjacency matrices should be:
1. Square matrices
2. All entries are either 0 or 1

#### #10: Returns -19 if the start node is encoded incorrectly (Functional)
Encoding for a node must be finite and represent an integer.

#### #11: Returns -29 if end node is encoded incorrectly (Functional)
Encoding for a node must be finite and represent an integer.

### #12: Nominal behavior (Container)

#### #3: Returns the number of edges in shortest path from startIdx to endIdx (Functional)
